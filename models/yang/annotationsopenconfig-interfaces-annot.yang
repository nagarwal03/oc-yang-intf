module openconfig-interfaces-annot {

    yang-version "1";

    namespace "http://openconfig.net/yang/annotation/openconfig-interfaces-annot";
    prefix "oc-interfaces-annot";

    import sonic-extensions { prefix sonic-ext; }
    import openconfig-interfaces { prefix oc-intf; }

    deviation /oc-intf:interfaces/oc-intf:interface {
        deviate add {
            sonic-ext:key-transformer "intf_tbl_key_xfmr";
            sonic-ext:table-transformer "intf_table_xfmr";
        }
    }

    deviation /oc-intf:interfaces/oc-intf:interface/oc-intf:state/oc-intf:admin-status {
        deviate add {
            sonic-ext:field-transformer "intf_admin_status_xfmr";
            sonic-ext:field-name "admin_status";
        }
    }

    deviation /oc-intf:interfaces/oc-intf:interface/oc-intf:config/oc-intf:enabled {
        deviate add {
            sonic-ext:field-transformer "intf_enabled_xfmr";
            sonic-ext:field-name "admin_status";
        }
    }

    deviation /oc-intf:interfaces/oc-intf:interface/oc-intf:state/oc-intf:enabled {
        deviate add {
            sonic-ext:field-transformer "intf_enabled_xfmr";
            sonic-ext:field-name "admin_status";
        }
    }

}
