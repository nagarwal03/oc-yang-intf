module openconfig-interfaces-private {

  yang-version "1";

  // namespace
  namespace "http://openconfig.net/yang/interfaces/private/extension";

  prefix "oc-intf-priv";

  // import some basic types
  import openconfig-interfaces { prefix oc-intf; }
  import openconfig-extensions { prefix oc-ext; }
  import openconfig-inet-types { prefix oc-inet; }
  import openconfig-if-ip {prefix oc-ip; }
  import openconfig-vlan-types { prefix oc-vlan-types; }
  import openconfig-yang-types { prefix oc-yang; }
  import openconfig-types { prefix oc-types; }

  organization
    "SONiC";

  contact
    "SONiC";

  description
    "This module describes a YANG model for openconfig-interfaces private yang definitions.";

  oc-ext:openconfig-version "0.0.3";

  revision "2021-09-09" {
    description
      "Add OpenConfig POSIX pattern extensions.";
    reference "0.0.3";
  }


  revision "2021-07-01" {
    description
      "Add YANG definitions for ARP/NDP RPC.";
    reference "0.0.2";
  }

  revision "2021-06-25" {
    description
      "Add YANG definitions for Gateway address attribute and RPCs.";
    reference "0.0.1";
  }


  typedef status {
      type enumeration {
          enum "SUCCESS" {
              description
                  "Indicates successful RPC call.";
          }
          enum ERROR {
              description
                  "Indicates error in RPC call execution.";
          }
      }
      description
          "Indicates 0 for SUCCESS and 1 for ERROR cases.";
  }

  augment "/oc-intf:interfaces/oc-intf:interface/oc-intf:subinterfaces/oc-intf:subinterface/oc-ip:ipv4/oc-ip:addresses/oc-ip:address/oc-ip:config" {
    description "Additional attributes for IPv4 address config container associated with an interface";
    leaf gw-addr {
      type oc-inet:ipv4-address;
      description "IPv4 Gateway address";
    }
  }

  augment "/oc-intf:interfaces/oc-intf:interface/oc-intf:subinterfaces/oc-intf:subinterface/oc-ip:ipv4/oc-ip:addresses/oc-ip:address/oc-ip:state" {
    description "Additional attributes for IPv4 address state container associated with an interface";
    leaf gw-addr {
      type oc-inet:ipv4-address;
      description "IPv4 Gateway address";
    }
  }


  augment "/oc-intf:interfaces/oc-intf:interface/oc-intf:subinterfaces/oc-intf:subinterface/oc-ip:ipv6/oc-ip:addresses/oc-ip:address/oc-ip:config" {
    description "Additional attributes for IPv6 address config container associated with an interface";
    leaf gw-addr {
      type oc-inet:ipv6-address;
      description "IPv6 Gateway address";
    }
  }

  augment "/oc-intf:interfaces/oc-intf:interface/oc-intf:subinterfaces/oc-intf:subinterface/oc-ip:ipv6/oc-ip:addresses/oc-ip:address/oc-ip:state" {
    description "Additional attributes for IPv6 address state container associated with an interface";
    leaf gw-addr {
      type oc-inet:ipv6-address;
      description "IPv6 Gateway address";
    }
  }
}
