module openconfig-interfaces-deviation {

  yang-version "1";

  // namespace
  namespace "http://openconfig.net/yang/interfaces/deviation/extension";

  prefix "oc-intf-dev";

  // import some basic types
  import openconfig-interfaces { prefix oc-intf; }
  import openconfig-extensions { prefix oc-ext; }
  import openconfig-if-ip {prefix oc-ip; }
  import openconfig-vlan { prefix oc-vlan; }
  import openconfig-if-ethernet {prefix oc-eth; }
  import openconfig-if-aggregate {prefix oc-lag; }
  import openconfig-if-tunnel {prefix oc-tun; }

  organization
    "SONiC";

  contact
    "SONiC";

  description
    "This module describes a YANG model for openconfig-interfaces deviations.";

  oc-ext:openconfig-version "0.1.0";

  revision "2024-01-19" {
    description
      "Add Yang deviations for unsupported interface attributes.";
    reference "0.1.0";
  }

  deviation /oc-intf:interfaces/oc-intf:interface/oc-intf:config/oc-intf:loopback-mode {
    deviate not-supported;
  }    

  deviation /oc-intf:interfaces/oc-intf:interface/oc-intf:config/oc-vlan:tpid {
    deviate not-supported;
  }    

  deviation /oc-intf:interfaces/oc-intf:interface/oc-intf:config/oc-intf:type {
    deviate not-supported;
  }   

  deviation /oc-intf:interfaces/oc-intf:interface/oc-intf:state/oc-intf:loopback-mode {
    deviate not-supported;
  }    

  deviation /oc-intf:interfaces/oc-intf:interface/oc-intf:state/oc-intf:oper-status {
    deviate not-supported;
  }    

  deviation /oc-intf:interfaces/oc-intf:interface/oc-intf:state/oc-intf:last-change {
    deviate not-supported;
  }       

  deviation /oc-intf:interfaces/oc-intf:interface/oc-intf:state/oc-intf:type {
    deviate not-supported;
  }   

  deviation /oc-intf:interfaces/oc-intf:interface/oc-intf:state/oc-intf:ifindex {
    deviate not-supported;
  }   

  deviation /oc-intf:interfaces/oc-intf:interface/oc-intf:state/oc-intf:logical {
    deviate not-supported;
  }   

  deviation /oc-intf:interfaces/oc-intf:interface/oc-intf:state/oc-vlan:tpid {
    deviate not-supported;
  }   

  deviation /oc-intf:interfaces/oc-intf:interface/oc-intf:state/oc-intf:counters/oc-intf:in-unknown-protos {
    deviate not-supported;
  }   
  
  deviation /oc-intf:interfaces/oc-intf:interface/oc-intf:state/oc-intf:counters/oc-intf:in-fcs-errors {
    deviate not-supported;
  }   

  deviation /oc-intf:interfaces/oc-intf:interface/oc-intf:state/oc-intf:counters/oc-intf:carrier-transitions {
    deviate not-supported;
  }

  deviation /oc-intf:interfaces/oc-intf:interface/oc-intf:state/oc-intf:counters/oc-intf:last-clear {
    deviate not-supported;
  }

  deviation /oc-intf:interfaces/oc-intf:interface/oc-intf:hold-time {
    deviate not-supported;
  }   

  deviation /oc-intf:interfaces/oc-intf:interface/oc-intf:subinterfaces/oc-intf:subinterface/oc-intf:state/oc-intf:ifindex {
    deviate not-supported;
  }

  deviation /oc-intf:interfaces/oc-intf:interface/oc-intf:subinterfaces/oc-intf:subinterface/oc-intf:state/oc-intf:admin-status {
    deviate not-supported;
  }
  
  deviation /oc-intf:interfaces/oc-intf:interface/oc-intf:subinterfaces/oc-intf:subinterface/oc-intf:state/oc-intf:name {
   deviate not-supported;
  }

  deviation /oc-intf:interfaces/oc-intf:interface/oc-intf:subinterfaces/oc-intf:subinterface/oc-intf:state/oc-intf:oper-status {
    deviate not-supported;
  }

  deviation /oc-intf:interfaces/oc-intf:interface/oc-intf:subinterfaces/oc-intf:subinterface/oc-intf:state/oc-intf:last-change {
    deviate not-supported;
  }

  deviation /oc-intf:interfaces/oc-intf:interface/oc-intf:subinterfaces/oc-intf:subinterface/oc-intf:state/oc-intf:logical {
    deviate not-supported;
  }

  deviation /oc-intf:interfaces/oc-intf:interface/oc-intf:subinterfaces/oc-intf:subinterface/oc-intf:state/oc-intf:counters {
    deviate not-supported;
  }
 
  deviation /oc-intf:interfaces/oc-intf:interface/oc-intf:subinterfaces/oc-intf:subinterface/oc-vlan:vlan {
    deviate not-supported;
  }
  
  deviation /oc-intf:interfaces/oc-intf:interface/oc-intf:subinterfaces/oc-intf:subinterface/oc-ip:ipv4/oc-ip:addresses/oc-ip:address/oc-ip:state/oc-ip:origin {
    deviate not-supported;
  }
 
  deviation /oc-intf:interfaces/oc-intf:interface/oc-intf:subinterfaces/oc-intf:subinterface/oc-ip:ipv4/oc-ip:addresses/oc-ip:address/oc-ip:vrrp {
    deviate not-supported;
  }
 
  deviation /oc-intf:interfaces/oc-intf:interface/oc-intf:subinterfaces/oc-intf:subinterface/oc-ip:ipv4/oc-ip:proxy-arp {
    deviate not-supported;
  }
 
  deviation /oc-intf:interfaces/oc-intf:interface/oc-intf:subinterfaces/oc-intf:subinterface/oc-ip:ipv4/oc-ip:neighbors {
    deviate not-supported;
  }
 
  deviation /oc-intf:interfaces/oc-intf:interface/oc-intf:subinterfaces/oc-intf:subinterface/oc-ip:ipv4/oc-ip:unnumbered {
    deviate not-supported;
  }
 
  deviation /oc-intf:interfaces/oc-intf:interface/oc-intf:subinterfaces/oc-intf:subinterface/oc-ip:ipv4/oc-ip:config {
    deviate not-supported;
  }
 
  deviation /oc-intf:interfaces/oc-intf:interface/oc-intf:subinterfaces/oc-intf:subinterface/oc-ip:ipv4/oc-ip:state {
    deviate not-supported;
  }
 
  deviation /oc-intf:interfaces/oc-intf:interface/oc-intf:subinterfaces/oc-intf:subinterface/oc-ip:ipv6/oc-ip:addresses/oc-ip:address/oc-ip:state/oc-ip:origin {
    deviate not-supported;
  }
 
  deviation /oc-intf:interfaces/oc-intf:interface/oc-intf:subinterfaces/oc-intf:subinterface/oc-ip:ipv6/oc-ip:addresses/oc-ip:address/oc-ip:state/oc-ip:status {
    deviate not-supported;
  }
 
  deviation /oc-intf:interfaces/oc-intf:interface/oc-intf:subinterfaces/oc-intf:subinterface/oc-ip:ipv6/oc-ip:addresses/oc-ip:address/oc-ip:vrrp {
    deviate not-supported;
  }
 
  deviation /oc-intf:interfaces/oc-intf:interface/oc-intf:subinterfaces/oc-intf:subinterface/oc-ip:ipv6/oc-ip:router-advertisement {
    deviate not-supported;
  }
 
  deviation /oc-intf:interfaces/oc-intf:interface/oc-intf:subinterfaces/oc-intf:subinterface/oc-ip:ipv6/oc-ip:neighbors {
    deviate not-supported;
  }
 
  deviation /oc-intf:interfaces/oc-intf:interface/oc-intf:subinterfaces/oc-intf:subinterface/oc-ip:ipv6/oc-ip:unnumbered {
    deviate not-supported;
  }

  deviation /oc-intf:interfaces/oc-intf:interface/oc-intf:subinterfaces/oc-intf:subinterface/oc-ip:ipv6/oc-ip:config/oc-ip:enabled {
    deviate replace {
      default false;
    }
  }
 
  deviation /oc-intf:interfaces/oc-intf:interface/oc-intf:subinterfaces/oc-intf:subinterface/oc-ip:ipv6/oc-ip:config/oc-ip:mtu {
    deviate not-supported;
  }
 
  deviation /oc-intf:interfaces/oc-intf:interface/oc-intf:subinterfaces/oc-intf:subinterface/oc-ip:ipv6/oc-ip:config/oc-ip:dup-addr-detect-transmits {
    deviate not-supported;
  }
 
  deviation /oc-intf:interfaces/oc-intf:interface/oc-intf:subinterfaces/oc-intf:subinterface/oc-ip:ipv6/oc-ip:config/oc-ip:dhcp-client {
    deviate not-supported;
  }
 
  deviation /oc-intf:interfaces/oc-intf:interface/oc-intf:subinterfaces/oc-intf:subinterface/oc-ip:ipv6/oc-ip:state/oc-ip:mtu {
    deviate not-supported;
  }
 
  deviation /oc-intf:interfaces/oc-intf:interface/oc-intf:subinterfaces/oc-intf:subinterface/oc-ip:ipv6/oc-ip:state/oc-ip:dup-addr-detect-transmits {
    deviate not-supported;
  }
 
  deviation /oc-intf:interfaces/oc-intf:interface/oc-intf:subinterfaces/oc-intf:subinterface/oc-ip:ipv6/oc-ip:state/oc-ip:dhcp-client {
    deviate not-supported;
  }
  
  deviation /oc-intf:interfaces/oc-intf:interface/oc-intf:subinterfaces/oc-intf:subinterface/oc-ip:ipv6/oc-ip:state/oc-ip:counters {
    deviate not-supported;
  }

  deviation /oc-intf:interfaces/oc-intf:interface/oc-eth:ethernet/oc-eth:config/oc-eth:mac-address {
    deviate not-supported;
  }

  deviation /oc-intf:interfaces/oc-intf:interface/oc-eth:ethernet/oc-eth:config/oc-eth:duplex-mode {
    deviate not-supported;
  }

  deviation /oc-intf:interfaces/oc-intf:interface/oc-eth:ethernet/oc-eth:config/oc-eth:enable-flow-control {
    deviate not-supported;
  }

  deviation /oc-intf:interfaces/oc-intf:interface/oc-eth:ethernet/oc-eth:state/oc-eth:mac-address {
    deviate not-supported;
  }

  deviation /oc-intf:interfaces/oc-intf:interface/oc-eth:ethernet/oc-eth:state/oc-eth:duplex-mode {
    deviate not-supported;
  }

  deviation /oc-intf:interfaces/oc-intf:interface/oc-eth:ethernet/oc-eth:state/oc-eth:enable-flow-control {
    deviate not-supported;
  }

  deviation /oc-intf:interfaces/oc-intf:interface/oc-eth:ethernet/oc-eth:state/oc-eth:hw-mac-address {
    deviate not-supported;
  }

  deviation /oc-intf:interfaces/oc-intf:interface/oc-eth:ethernet/oc-eth:state/oc-eth:negotiated-duplex-mode {
    deviate not-supported;
  }

  deviation /oc-intf:interfaces/oc-intf:interface/oc-eth:ethernet/oc-eth:state/oc-eth:negotiated-port-speed {
    deviate not-supported;
  }

  deviation /oc-intf:interfaces/oc-intf:interface/oc-eth:ethernet/oc-vlan:switched-vlan {
    deviate not-supported;
  }
  
  deviation /oc-intf:interfaces/oc-intf:interface/oc-lag:aggregation/oc-vlan:switched-vlan {
    deviate not-supported;
  }

  deviation /oc-intf:interfaces/oc-intf:interface/oc-lag:aggregation/oc-lag:state/oc-lag:lag-speed {
    deviate not-supported;
  }

  deviation /oc-intf:interfaces/oc-intf:interface/oc-lag:aggregation/oc-lag:state/oc-lag:member {
        deviate not-supported;
  }
  
  deviation /oc-intf:interfaces/oc-intf:interface/oc-eth:ethernet/oc-eth:state/oc-eth:counters/oc-eth:in-mac-control-frames {
    deviate not-supported;
  }

  deviation /oc-intf:interfaces/oc-intf:interface/oc-eth:ethernet/oc-eth:state/oc-eth:counters/oc-eth:in-mac-pause-frames {
    deviate not-supported;
  }

  deviation /oc-intf:interfaces/oc-intf:interface/oc-eth:ethernet/oc-eth:state/oc-eth:counters/oc-eth:in-8021q-frames {
    deviate not-supported;
  }

  deviation /oc-intf:interfaces/oc-intf:interface/oc-eth:ethernet/oc-eth:state/oc-eth:counters/oc-eth:in-crc-errors {
    deviate not-supported;
  }

  deviation /oc-intf:interfaces/oc-intf:interface/oc-eth:ethernet/oc-eth:state/oc-eth:counters/oc-eth:in-block-errors {
    deviate not-supported;
  }

  deviation /oc-intf:interfaces/oc-intf:interface/oc-eth:ethernet/oc-eth:state/oc-eth:counters/oc-eth:out-mac-control-frames {
    deviate not-supported;
  }

  deviation /oc-intf:interfaces/oc-intf:interface/oc-eth:ethernet/oc-eth:state/oc-eth:counters/oc-eth:out-mac-pause-frames {
    deviate not-supported;
  }

  deviation /oc-intf:interfaces/oc-intf:interface/oc-eth:ethernet/oc-eth:state/oc-eth:counters/oc-eth:out-8021q-frames {
    deviate not-supported;
  }

  deviation /oc-intf:interfaces/oc-intf:interface/oc-tun:tunnel {
    deviate not-supported;
  }

  deviation /oc-intf:interfaces/oc-intf:interface/oc-vlan:routed-vlan {
    deviate not-supported;
  }
 
}
