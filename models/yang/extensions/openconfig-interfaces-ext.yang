module openconfig-interfaces-ext {

    yang-version "1.1";

    // namespace
    namespace "http://openconfig.net/yang/interfaces/extension";

    prefix "oc-intf-ext";

    import openconfig-extensions { prefix oc-ext; }
    import openconfig-interfaces { prefix oc-intf; }
    import openconfig-vlan { prefix oc-vlan; }
    import openconfig-if-ethernet {prefix oc-eth; }
    import openconfig-if-aggregate {prefix oc-lag; }
    import openconfig-if-tunnel {prefix oc-tun; }
    

    organization "SONiC";

    contact
        "SONiC";

    description
        "This module contains collection of yang definitions for extensions to
         openconfig-interfaces yang";

    oc-ext:openconfig-version "0.1.0";

    revision 2020-06-23 {
        description
         "Initial version.";
        reference "0.1.0";
    }

    deviation /oc-intf:interfaces/oc-intf:interface/oc-intf:config/oc-intf:loopback-mode {
	     deviate not-supported;
    }    

    deviation /oc-intf:interfaces/oc-intf:interface/oc-intf:config/oc-vlan:tpid {
	     deviate not-supported;
    }    

    deviation /oc-intf:interfaces/oc-intf:interface/oc-intf:config/oc-intf:type {
	     deviate not-supported;
    }   


    deviation /oc-intf:interfaces/oc-intf:interface/oc-intf:state/oc-intf:loopback-mode {
	     deviate not-supported;
    }    

    deviation /oc-intf:interfaces/oc-intf:interface/oc-intf:state/oc-intf:oper-status {
	     deviate not-supported;
    }    

    deviation /oc-intf:interfaces/oc-intf:interface/oc-intf:state/oc-intf:last-change {
	     deviate not-supported;
    }    

    deviation /oc-intf:interfaces/oc-intf:interface/oc-intf:state/oc-intf:counters {
	     deviate not-supported;
    }    

    deviation /oc-intf:interfaces/oc-intf:interface/oc-intf:state/oc-intf:type {
	     deviate not-supported;
    }   

    deviation /oc-intf:interfaces/oc-intf:interface/oc-intf:state/oc-intf:ifindex {
	     deviate not-supported;
    }   

    deviation /oc-intf:interfaces/oc-intf:interface/oc-intf:state/oc-intf:logical {
	     deviate not-supported;
    }   

        deviation /oc-intf:interfaces/oc-intf:interface/oc-intf:state/oc-vlan:tpid {
	     deviate not-supported;
    }   

    deviation /oc-intf:interfaces/oc-intf:interface/oc-intf:hold-time {
	     deviate not-supported;
    }   

    deviation /oc-intf:interfaces/oc-intf:interface/oc-eth:ethernet/oc-eth:config/oc-eth:mac-address {
        deviate not-supported;
    }

    deviation /oc-intf:interfaces/oc-intf:interface/oc-eth:ethernet/oc-eth:config/oc-eth:standalone-link-training {
        deviate not-supported;
    }

    deviation /oc-intf:interfaces/oc-intf:interface/oc-eth:ethernet/oc-eth:config/oc-eth:duplex-mode {
        deviate not-supported;
    }

    deviation /oc-intf:interfaces/oc-intf:interface/oc-eth:ethernet/oc-eth:config/oc-eth:enable-flow-control {
        deviate not-supported;
    }

    deviation /oc-intf:interfaces/oc-intf:interface/oc-eth:ethernet/oc-eth:config/oc-eth:fec-mode {
        deviate not-supported;
    }

    deviation /oc-intf:interfaces/oc-intf:interface/oc-eth:ethernet/oc-eth:config/oc-lag:aggregate-id {
        deviate not-supported;
    }

    deviation /oc-intf:interfaces/oc-intf:interface/oc-eth:ethernet/oc-eth:state/oc-eth:mac-address {
        deviate not-supported;
    }

    deviation /oc-intf:interfaces/oc-intf:interface/oc-eth:ethernet/oc-eth:state/oc-eth:standalone-link-training {
        deviate not-supported;
    }

    deviation /oc-intf:interfaces/oc-intf:interface/oc-eth:ethernet/oc-eth:state/oc-eth:duplex-mode {
        deviate not-supported;
    }

    deviation /oc-intf:interfaces/oc-intf:interface/oc-eth:ethernet/oc-eth:state/oc-eth:enable-flow-control {
        deviate not-supported;
    }

    deviation /oc-intf:interfaces/oc-intf:interface/oc-eth:ethernet/oc-eth:state/oc-eth:fec-mode {
        deviate not-supported;
    }

    deviation /oc-intf:interfaces/oc-intf:interface/oc-eth:ethernet/oc-eth:state/oc-eth:counters {
        deviate not-supported;
    }

    deviation /oc-intf:interfaces/oc-intf:interface/oc-eth:ethernet/oc-eth:state/oc-lag:aggregate-id {
        deviate not-supported;
    }

    deviation /oc-intf:interfaces/oc-intf:interface/oc-eth:ethernet/oc-eth:state/oc-eth:hw-mac-address {
        deviate not-supported;
    }

    deviation /oc-intf:interfaces/oc-intf:interface/oc-eth:ethernet/oc-eth:state/oc-eth:negotiated-duplex-mode {
        deviate not-supported;
    }

    deviation /oc-intf:interfaces/oc-intf:interface/oc-eth:ethernet/oc-eth:state/oc-eth:negotiated-port-speed {
        deviate not-supported;
    }

    deviation /oc-intf:interfaces/oc-intf:interface/oc-eth:ethernet/oc-vlan:switched-vlan {
        deviate not-supported;
    }

    deviation /oc-intf:interfaces/oc-intf:interface/oc-tun:tunnel {
        deviate not-supported;
    }

    deviation /oc-intf:interfaces/oc-intf:interface/oc-lag:aggregation {
        deviate not-supported;
    }

    deviation /oc-intf:interfaces/oc-intf:interface/oc-vlan:routed-vlan {
        deviate not-supported;
    }

}
